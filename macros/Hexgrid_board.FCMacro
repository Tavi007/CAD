import sys
import importlib

lib_path = "C:\\CAD\\projects\\macros\\lib\\"
if lib_path not in sys.path:
    sys.path.append(lib_path)
import lib
importlib.reload(lib)
import lib.grid
importlib.reload(lib.grid)
import lib.shapes
importlib.reload(lib.shapes)

from lib.grid.generator import get_shapes
from lib.grid.grid_type import GridType
from lib.shapes.abstract_polygon import AbstractPolygon
from lib.shapes.shape import Shape
from lib.shapes.rectangle import Rectangle

import FreeCAD as App
import Part
import math


RESOURCE_UNIT_LENGTH = 10
TOL=0.3

def main():
    tableau_shape=Rectangle(-100,-75, 200, 150)
    grid_type=GridType.SQUARE
    height=2
    
    tableau = create_resource_tableau(tableau_shape, grid_type, height)
    if tableau:
        doc = App.newDocument()
        obj = doc.addObject("Part::Feature", "ResourceTableau")
        obj.Shape = tableau
        doc.recompute()
    else:
        print("tableau creation failed")
        
    

def create_resource(grid_type: GridType, height: int):
    shape = get_shape(grid_type, 0, 0, RESOURCE_UNIT_LENGTH)
    return create_shape_part(shape, height)

def create_shape_part(shape: AbstractPolygon, height: int):
    vertices = shape.get_vertices()
    points=[]
    for x, y in vertices:
        points.append(App.Vector(x,y,0))
        
    wire = Part.makePolygon(points + [points[0]])
    face = Part.Face(wire)
    return face.extrude(App.Vector(0, 0, height))

def create_resource_tableau(tableau_shape: Shape, grid_type: GridType, height: int):
    tableau = create_shape_part(tableau_shape, height)
    negative_shapes = get_shapes(grid_type, RESOURCE_UNIT_LENGTH+TOL, tableau_shape.is_inside)
    no_shapes = len(negative_shapes)
    for i, shape in enumerate(negative_shapes):
        negative = create_shape_part(shape, height)
        tableau = tableau.cut(negative)
        print(f"Shape {i} from {no_shapes} cut from tableau")
    return tableau

if __name__ == "__main__":
    main()
