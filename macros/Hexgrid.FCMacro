from lib.shapes.shape_type import ShapeType
from lib.shapes.abstract_polygon import AbstractPolygon
from lib.grid.grid_type import GridType
import math
from pathlib import Path

import numpy as np
import re
import Mesh
import Part
import FreeCAD as App
import sys
import importlib
from shapely import Polygon

import lib.io
import lib.shapes
import lib.grid
import lib
lib_path = "C:\\CAD\\projects\\macros\\lib\\"
if lib_path not in sys.path:
    sys.path.append(lib_path)
importlib.reload(lib)
importlib.reload(lib.grid)
importlib.reload(lib.shapes)
importlib.reload(lib.io)

# from lib.io.lattice_points_io import read_lattice_indices


GAP_SIZE = 3.0
RESOURCE_SIZE = 16.0
UNIT_LENGTH = GAP_SIZE + RESOURCE_SIZE
TOL = 0.3
SIDE_HOLE_HEIGHT = 0.1
SIDE_HOLE_WIDTH = 0.31
SQRT3 = math.sqrt(3)
HEIGHT = 2.3


def main():
    print("=========== Start generating ===========")
    grid_type = GridType.PACKED

    #stencil_dir = Path(f"C:/CAD/projects/macros/output/stencil/hexagon/")
    # create_stencils(stencil_dir)

    board_path = Path(
        f"C:/CAD/projects/macros/output/unit_length_{RESOURCE_SIZE}/board/triangle/packed/150x150.txt")
    # board_path = Path("C:/CAD/projects/macros/output/test.txt")
    create_board(board_path)


def create_stencils(input_dir: Path):
    print(f"start stencil creation of {input_dir}")
    base_path = input_dir / "base.txt"
    base_lattice_indices = read_lattice_indices(base_path)

    for stencil_path in input_dir.rglob("*.txt"):
        if not re.fullmatch(r"\d+\.txt", stencil_path.name):
            continue

        print(f" - start stencil creation of {stencil_path}")
        hole_lattice_indices = read_lattice_indices(stencil_path)
        stencil = create_shape_with_holes(
            GridType.PACKED, base_lattice_indices, hole_lattice_indices)

        if stencil:
            save(stencil, stencil_path)
            print(f" - - stencil creation of {input} succeeded")
        else:
            print(f" - - stencil creation of {input} failed")


def create_board(input: Path):
    print(f"start tableau creation of {input}")
    lattice_indices = read_lattice_indices(input)
    tableau = create_shape_with_holes(
        GridType.PACKED, lattice_indices, lattice_indices)
    if tableau:
        save(tableau, input)
        print(f" - tableau creation of {input} succeeded")
    else:
        print(f" - tableau creation of {input} failed")


def save(shape, input: Path):
    name = f"{input.parent}_{input.name}"
    doc = App.newDocument()
    obj = doc.addObject("Part::Feature", name)
    obj.Shape = shape
    doc.recompute()

    Mesh.export(
        [obj],
        str(input.with_suffix(".stl"))
    )
    App.closeDocument(doc.Name)


def read_lattice_indices(filename: Path) -> list[tuple[int, int]]:
    lattice_points = []
    with open(filename, "r") as f:
        for line in f:
            x_str, y_str = line.strip().split(",")
            lattice_points.append((int(x_str), int(y_str)))
    return lattice_points


def create_shape_with_holes(
    grid_type: GridType,
    hex_lattice_indices: list[tuple[int, int]],
    hole_lattice_indices: list[tuple[int, int]],
):
    hex_shapes = []
    for (i, j) in hex_lattice_indices:
        hex = create_base_shape(ShapeType.HEXAGON_POINTY,
                                UNIT_LENGTH*2/SQRT3, UNIT_LENGTH*2/SQRT3, HEIGHT)
        center = get_center(grid_type, i, j)
        hex.translate(center)
        hex_shapes.append(hex)

    holes = []
    for (i, j) in hole_lattice_indices:
        hole = create_base_shape(
            ShapeType.CIRCLE, RESOURCE_SIZE+TOL, RESOURCE_SIZE+TOL, HEIGHT)
        center = get_center(grid_type, i, j)
        hole.translate(center)
        holes.append(hole)

    tableau = None
    for hex in hex_shapes:
        if not tableau:
            tableau = hex
        else:
            tableau = tableau.fuse(hex)
    for hole in holes:
        tableau = tableau.cut(hole)
    return tableau


def create_base_shape(shape_type: ShapeType, width: int, depth: int, height: int):
    board_shape = shape_type.get_board_shape(width, depth)
    if shape_type == ShapeType.CIRCLE:
        return Part.makeCylinder(board_shape.radius, height)
    else:
        polygon: Polygon = board_shape.to_shapely()
        points = [
            App.Vector(x, y, 0)
            for x, y in polygon.exterior.coords
        ]
        wire = Part.makePolygon(points)
        face = Part.Face(wire)
        return face.extrude(App.Vector(0, 0, height))


def get_center(grid_type: GridType, i: int, j: int):
    unit_vector = grid_type.get_unit_vector()
    steps = np.array([i, j])
    center = UNIT_LENGTH * unit_vector @ steps
    return App.Vector(center[0], center[1], 0.0)


def get_side_holes(center, height: float):
    apothem = UNIT_LENGTH * math.sqrt(3) / 2

    holes = []
    for k in range(6):
        angle = math.radians(60 * k + 30)

        nx = math.cos(angle)
        ny = math.sin(angle)

        mx = apothem * nx
        my = apothem * ny

        hole = Part.makeBox(SIDE_HOLE_WIDTH, UNIT_LENGTH*2, SIDE_HOLE_HEIGHT)
        translation = App.Vector(
            center[0] - SIDE_HOLE_WIDTH/2 - SIDE_HOLE_WIDTH*nx/2,
            center[1] - SIDE_HOLE_WIDTH*ny/2,
            (height - SIDE_HOLE_HEIGHT) / 2
        )
        rot = App.Rotation(
            App.Vector(1, 0, 0),
            App.Vector(nx, ny, 0)
        )
        hole.Placement = App.Placement(translation, rot)
        holes.append(hole)
    return holes


if __name__ == "__main__":
    main()
