import FreeCAD as App
import Part
from math import sqrt, pi
from dataclasses import dataclass
import itertools

# measurements + clearance
catastrophes_and_bol = 11 + 2
ages = 15 + 1
#catastrophes_and_bol + ages # < 31.5 

#measurements traits = 43 
traits = 74.5 - catastrophes_and_bol - ages # > 43 <=>

# catastrophes_and_bol + ages + traits = 74.5 <=> 
#sum_height = 82 = catastrophes_and_bol + ages + traits + 2.5*3



#overlushed = 20
Meaning_of_life = 10
magical_merchants = 18.5



# =====================
# PARAMETERS
# =====================

# printer
MAX_WIDTH = 220
MAX_DEPTH = 220
MAX_HEIGHT = 220


# Tray
NO_TRAYS = 1

BUMP_HEIGHT = 1
SLIT_WIDTH = 25
SEPERATOR_WIDTH = 1.75
CORNER_ROUNDING_RADIUS = 10
BOTTOM_THICKNESS = 2.5

# card dimensions
CARD_WIDTH = 64.0
CARD_HEIGHT = 89.0
NO_CARDS = 100
CARD_DEPTH = 0.3

# final height is STACK_SIZE + BOTTOM_THICKNESS
# Effective stack size is STACK_SIZE - BUMP_HEIGHT
#STACK_SIZE = NO_CARDS * CARD_DEPTH + BUMP_HEIGHT 
STACK_SIZE = Meaning_of_life + BUMP_HEIGHT

CARD_TOLERANCE = 2
CARD_FILLET = 2

# magnet holes
ADD_MAGNETS_TOP = True
ADD_MAGNETS_BOT = True
ADD_MAGNETS_SIDE = False
MAGNET_RADIUS = 3
MAGNET_DEPTH = 3.0
MAGNET_CLEARANCE = 0.3
SIDE_MAGNET_Z = None

# sticker holes
ADD_STICKER_TOP = True
ADD_STICKER_SIDE = False
RADIUS_STICKER_TOP = 5
RADIUS_STICKER_SIDE = 18
STICKER_CLEARANCE = 0.3
STICKER_DEPTH = 0.4



# outer hull
TOP_WALL_THICKNESS = SEPERATOR_WIDTH
BOT_WALL_THICKNESS = SEPERATOR_WIDTH
if ADD_MAGNETS_TOP or ADD_MAGNETS_BOT or ADD_MAGNETS_SIDE:
    minimum_thickness = (MAGNET_RADIUS + MAGNET_CLEARANCE) * 2 + 2 + SEPERATOR_WIDTH
    TOP_WALL_THICKNESS = max(TOP_WALL_THICKNESS, minimum_thickness)
    BOT_WALL_THICKNESS = max(BOT_WALL_THICKNESS, minimum_thickness)

if ADD_STICKER_TOP:
    minimum_thickness = (RADIUS_STICKER_TOP + STICKER_CLEARANCE) * 2 + 2 + SEPERATOR_WIDTH
    TOP_WALL_THICKNESS = max(TOP_WALL_THICKNESS, minimum_thickness)



def get_inner_sizes():
    width = CARD_WIDTH + CARD_TOLERANCE
    depth = CARD_HEIGHT + CARD_TOLERANCE
    height = STACK_SIZE
    return width, depth, height





# =====================
# DATA STRUCTURES
# =====================

@dataclass
class Cylinder:
    position: App.Vector
    radius: float
    height: float
    direction: App.Vector


# =====================
# MAIN
# =====================

def main():
    if NO_TRAYS < 1:
        return

    shape = create_card_holder()
    if not shape:
        print("Shape won't fit in the print volume!")
        return

    doc = App.ActiveDocument
    if doc is None:
        doc = App.newDocument("CardTrays")

    obj = doc.addObject("Part::Feature", "CardTrays")
    obj.Shape = shape
    doc.recompute()


# =====================
# CARD HOLDER
# =====================

def create_card_holder():
    tray_negative = create_card_tray_negatives()
    inner_width, inner_depth, inner_height = get_inner_sizes()

    outer_width = inner_width * NO_TRAYS + (NO_TRAYS + 1) * SEPERATOR_WIDTH
    outer_depth = inner_depth + TOP_WALL_THICKNESS + BOT_WALL_THICKNESS
    outer_height = inner_height + BOTTOM_THICKNESS

    outer_box = Part.makeBox(outer_width, outer_depth, outer_height)
    outer_box = outer_box.makeFillet(SEPERATOR_WIDTH/2, outer_box.Edges)

    # helper geometries
    translation = App.Vector(SEPERATOR_WIDTH, BOT_WALL_THICKNESS, BOTTOM_THICKNESS)
    tray_negative = tray_negative.translate(translation)
    
    
    # First tray
    outer_box = outer_box.cut(tray_negative)

    # Additional trays
    if NO_TRAYS > 1:
        for _ in range(NO_TRAYS - 1):
            tray_negative = tray_negative.translate(
                App.Vector(inner_width + SEPERATOR_WIDTH, 0, 0)
            )
            outer_box = outer_box.cut(tray_negative)
            

    outer_box = cut_magnet_holes(outer_box, outer_width, outer_depth, outer_height)
    outer_box = cut_sticker_holes(outer_box, outer_width, outer_depth, outer_height)
    

    print(f"Dimensions: {outer_width} x {outer_depth} x {outer_height} mm³")

    return outer_box


# =====================
# TRAY NEGATIVE
# =====================

def create_card_tray_negatives():
    width, depth, height = get_inner_sizes()
    b_depth = depth / 8

    base = Part.makeBox(width, depth, height)
    
    # round bottom edges
    bottom_edges = []
    for edge in base.Edges:
        z_values = [v.Point.z for v in edge.Vertexes]
        if all(abs(z) < 1E-6 for z in z_values):
            bottom_edges.append(edge)    
    base = base.makeFillet(CARD_FILLET, bottom_edges)

    # bumps
    bump = Part.makeBox(SLIT_WIDTH, b_depth, BUMP_HEIGHT)
    bump = bump.translate(App.Vector((width - SLIT_WIDTH)/2, b_depth * 2, 0))
    base = base.cut(bump)
    bump = bump.translate(App.Vector(0, b_depth * 3, 0))
    base = base.cut(bump)

    cutout = get_finger_cut_out()
    base = base.fuse(cutout)
    
    return base
    
    
def get_finger_cut_out():
    width, depth, height = get_inner_sizes()

    # cut out for finger
    cutout = Part.makeBox(SLIT_WIDTH, BOT_WALL_THICKNESS + 2, height)
    cutout = cutout.translate(App.Vector((width - SLIT_WIDTH)/2, -BOT_WALL_THICKNESS, 0))
    
    # round corner of cutout
    corner_cut = Part.makeBox(SLIT_WIDTH + 2*CORNER_ROUNDING_RADIUS, BOT_WALL_THICKNESS, CORNER_ROUNDING_RADIUS)
    corner_cut = corner_cut.cut(create_hole(Cylinder(
        position=App.Vector(0, 0, 0),
        radius=CORNER_ROUNDING_RADIUS,
        height=BOT_WALL_THICKNESS,
        direction=App.Vector(0, 1, 0)
    )))
    corner_cut = corner_cut.cut(create_hole(Cylinder(
        position=App.Vector(SLIT_WIDTH + 2*CORNER_ROUNDING_RADIUS, 0, 0),
        radius=CORNER_ROUNDING_RADIUS,
        height=BOT_WALL_THICKNESS,
        direction=App.Vector(0, 1, 0)
    )))
    corner_cut.translate(App.Vector((width-SLIT_WIDTH)/2 - CORNER_ROUNDING_RADIUS, -BOT_WALL_THICKNESS, height-CORNER_ROUNDING_RADIUS))
    cutout = cutout.fuse(corner_cut)
    return cutout


# =====================
# MAGNET HOLES
# =====================

def cut_magnet_holes(card_holder, width, depth, height):
    cylinders = []
    if ADD_MAGNETS_TOP:
        cylinders.extend(create_corner_magnets_top(width, depth, height))
    if ADD_MAGNETS_BOT:
        cylinders.extend(create_corner_magnets_bot(width, depth, height))
    if ADD_MAGNETS_SIDE:
        if SIDE_MAGNET_Z:
            z_position = SIDE_MAGNET_Z
        else:
            z_position = height/2
        cylinders.extend(create_side_wall_magnets(width, depth, height, z_position))

    for cyl in cylinders:
        hole = create_hole(cyl)
        card_holder = card_holder.cut(hole)

    return card_holder


def create_corner_magnets_top(width, depth, height):
    dx = BOT_WALL_THICKNESS / 2 + 0.75
    dy = BOT_WALL_THICKNESS / 2

    x_positions = [dx, width - dx]
    y_positions = [dy, depth - dy]
    z = height - MAGNET_DEPTH

    cylinders = []
    for x, y in itertools.product(x_positions, y_positions):
        cylinders.append(
            Cylinder(
                position=App.Vector(x, y, z),
                radius=MAGNET_RADIUS + MAGNET_CLEARANCE,
                height=MAGNET_DEPTH + MAGNET_CLEARANCE / 2,
                direction=App.Vector(0, 0, 1)
            )
        )
    return cylinders


def create_corner_magnets_bot(width, depth, height):
    dx = BOT_WALL_THICKNESS / 2 + 0.75
    dy = BOT_WALL_THICKNESS / 2

    x_positions = [dx, width - dx]
    y_positions = [dy, depth - dy]
    z = 0

    cylinders = []
    for x, y in itertools.product(x_positions, y_positions):
        cylinders.append(
            Cylinder(
                position=App.Vector(x, y, z),
                radius=MAGNET_RADIUS + MAGNET_CLEARANCE,
                height=MAGNET_DEPTH + MAGNET_CLEARANCE / 2,
                direction=App.Vector(0, 0, 1)
            )
        )
    return cylinders


def create_side_wall_magnets(width, depth, height, z):
    
    dy = SEPERATOR_WIDTH + MAGNET_RADIUS + MAGNET_CLEARANCE

    specs = [
        (0, dy, App.Vector(1, 0, 0)),   # left front
        (0, depth - dy, App.Vector(1, 0, 0)),  # left back
        (width, dy, App.Vector(-1, 0, 0)),  # right front
        (width, depth - dy, App.Vector(-1, 0, 0)),  # right back
    ]

    cylinders = []
    for x, y, direction in specs:
        cylinders.append(
            Cylinder(
                position=App.Vector(x, y, z),
                radius=MAGNET_RADIUS + MAGNET_CLEARANCE,
                height=MAGNET_DEPTH + MAGNET_CLEARANCE / 2,
                direction=direction
            )
        )

    return cylinders


# =====================
# STICKER HOLES
# =====================

def cut_sticker_holes(card_holder, width, depth, height):
    cylinders = []
    if ADD_STICKER_TOP:
        cylinders.extend(create_top_sticker(width, depth, height))
    if ADD_STICKER_SIDE:
        cylinders.extend(create_side_sticker(width, depth, height))

    for cyl in cylinders:
        hole = create_hole(cyl)
        card_holder = card_holder.cut(hole)

    return card_holder
    
def create_top_sticker(width, depth, height):
    x = width/2
    y = depth - RADIUS_STICKER_TOP - STICKER_CLEARANCE - SEPERATOR_WIDTH/2 - 1.4
    z = height - STICKER_DEPTH

    cylinder = Cylinder(
        position=App.Vector(x, y, z),
        radius=RADIUS_STICKER_TOP + STICKER_CLEARANCE,
        height=STICKER_DEPTH + STICKER_CLEARANCE / 2,
        direction=App.Vector(0, 0, 1)
    )
    return [cylinder]
    
def create_side_sticker(width, depth, height):
    y = depth/2
    z = height/2
    
    cylinders = [Cylinder(
            position=App.Vector(0, y, z),
            radius=RADIUS_STICKER_SIDE + STICKER_CLEARANCE,
            height=STICKER_DEPTH + STICKER_CLEARANCE / 2,
            direction=App.Vector(1, 0, 0)
        ),
        Cylinder(
            position=App.Vector(width, y, z),
            radius=RADIUS_STICKER_SIDE + STICKER_CLEARANCE,
            height=STICKER_DEPTH + STICKER_CLEARANCE / 2,
            direction=App.Vector(-1, 0, 0)
        )]
    return cylinders


def create_hole(cylinder: Cylinder):
    hole = Part.makeCylinder(cylinder.radius, cylinder.height)

    if cylinder.direction != App.Vector(0, 0, 1):
        axis = App.Vector(0, 0, 1).cross(cylinder.direction)
        angle = App.Vector(0, 0, 1).getAngle(cylinder.direction)
        hole.rotate(App.Vector(0, 0, 0), axis, angle * 180 / pi)

    hole.translate(cylinder.position)
    return hole
    



# =====================
# ENTRY POINT
# =====================

if __name__ == "__main__":
    main()
